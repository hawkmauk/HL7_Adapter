package CIM_Structure {
    doc
    /* Project-agnostic CIM skeleton showing required package structure for conforming CIM models. */

    package Domain {
        doc /* Domain ontology: conceptual elements, relationships, and taxonomies. */
    }

    package Stakeholders {
        doc /* Stakeholders and actor concepts interacting with or governing the system. */
    }

    package Context {
        doc /* Black-box operational context, environment, and external systems. */
    }

    package Actions {
        doc /* High-level operational activities, flows, and scenarios. */
    }

    package Mission {
        doc /* Mission outcomes, objectives, and success criteria. */
    }

    package Assumptions {
        doc /* Non-design assumptions and constraints shaping the solution space. */
    }
}
