package MDA {

    private import MDA_Structure::*;
    private import MDA_View::*;
    private import MDA_Lifecycle::*;
    private import MDA_CIM::*;
    private import MDA_PIM::*;
    private import MDA_PSM::*;

    alias Structure for MDA_Structure;
    alias Views for MDA_View;
    alias Lifecycle for MDA_Lifecycle;
    alias CIM for MDA_CIM;
    alias PIM for MDA_PIM;
    alias PSM for MDA_PSM;
}
