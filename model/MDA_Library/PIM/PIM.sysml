package MDA_PIM {

    private import PIM_Structure::*;
    private import PIM_View::*;
    private import PIM_Viewpoint::*;

    alias Structure for PIM_Structure;
    alias View for PIM_View;
    alias Viewpoint for PIM_Viewpoint;
}
