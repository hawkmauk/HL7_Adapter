package PIM_Structure {

    doc
    /* Project-agnostic PIM skeleton showing the expected package structure
       for conforming PIM models. Focuses on logical solution design that
       is independent of any particular platform or technology stack.
     */

    package LogicalArchitecture {
        doc /* Logical components, connectors, and white-box structure of the system-of-interest. */
    }

    package Interfaces {
        doc /* Logical service and protocol interfaces, ports, and message contracts between components and external actors. */
    }

    package Behavior {
        doc /* Platform-independent behaviors such as activities, sequences, state machines, and scenarios. */
    }

    package DataModel {
        doc /* Logical information model and data structures, independent of storage or serialization technology. */
    }

    package Requirements {
        doc /* PIM-level requirements and constraints derived from CIM mission and stakeholder needs. */
    }

    package Allocations {
        doc /* Allocations from PIM requirements to logical architecture, interfaces, and behaviors. */
    }

    package Verification {
        doc /* PIM-level verification objectives, cases, and coverage intent prior to PSM realization. */
    }
}
