package PSM_Viewpoint {
    
    private import Views::*;
    private import MDA_Viewpoint::*;

    package PSMStandardViewpointCatalog {
        doc /* PSM-specific viewpoint catalog specializing the abstract lifecycle documentation contract. */

        viewpoint def PlatformRealizationViewpoint :> ArchitectureAndBehaviorViewpoint {
            doc /* Covers technology-specific implementation and deployment realization details. */
        }

        viewpoint def OperationalReadinessViewpoint :> LifecycleGateReadinessViewpoint {
            doc /* Covers release readiness, operational transition, and production signoff evidence. */
        }

        viewpoint def VerificationEvidenceViewpoint :> VerificationAndComplianceViewpoint {
            doc /* Covers concrete test evidence, compliance outcomes, and residual risk posture. */
        }

        viewpoint def CodeRealizationViewpoint :> ExecutableViewpoint {
            doc /* Covers model content selected for code or other executable artifact generation. */
        }

        viewpoint def TestRealizationViewpoint :> TestViewpoint {
            doc /* Covers model content selected for TypeScript test artifact generation from verification cases. */
        }
    }
}
