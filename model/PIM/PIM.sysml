package PIM {

    alias LogicalArchitecture for PIM_LogicalArchitecture;
    alias Requirements for PIM_Requirements;
    alias Interfaces for PIM_Interfaces;
    alias Allocations for PIM_Allocations;
    alias Behavior for PIM_Behavior;
    alias UseCases for PIM_UseCases;
    alias Parametrics for PIM_Parametrics;

}
