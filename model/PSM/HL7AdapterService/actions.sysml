package PSM_HL7AdapterService_Actions {

    private import PSM_MLLPReceiver_Actions::*;
    private import PSM_Parser_Actions::*;
    private import PSM_Transformer_Actions::*;
    private import PSM_HTTPForwarder_Actions::*;
    private import PSM_ErrorHandler_Actions::*;
    private import PSM_HL7AdapterService_Interfaces::*;
    private import PSM_HL7AdapterService::*;

    doc /* PSM action definitions. Component actions live in per-component packages; this package re-exports them and defines BootstrapAdapter. */

    alias ParseMllpFrame for PSM_MLLPReceiver_Actions::ParseMllpFrame;
    alias BuildMllpMessage for PSM_MLLPReceiver_Actions::BuildMllpMessage;
    alias BuildAck for PSM_MLLPReceiver_Actions::BuildAck;
    alias BuildNak for PSM_MLLPReceiver_Actions::BuildNak;
    alias StartReceiver for PSM_MLLPReceiver_Actions::StartReceiver;
    alias StopReceiver for PSM_MLLPReceiver_Actions::StopReceiver;
    alias InitializeMLLPReceiver for PSM_MLLPReceiver_Actions::InitializeMLLPReceiver;

    alias ParseHL7Message for PSM_Parser_Actions::ParseHL7Message;
    alias HandleIncomingHL7 for PSM_Parser_Actions::HandleIncomingHL7;
    alias InitializeParser for PSM_Parser_Actions::InitializeParser;

    alias TransformToJSON for PSM_Transformer_Actions::TransformToJSON;
    alias HandleTransformRequest for PSM_Transformer_Actions::HandleTransformRequest;
    alias InitializeTransformer for PSM_Transformer_Actions::InitializeTransformer;

    alias InitializeHTTPForwarder for PSM_HTTPForwarder_Actions::InitializeHTTPForwarder;
    alias InitializeErrorHandler for PSM_ErrorHandler_Actions::InitializeErrorHandler;

    alias MLLPIngressBinding for PSM_HL7AdapterService_Interfaces::PSM_MLLPIngressPort;
    alias HTTPEgressBinding for PSM_HL7AdapterService_Interfaces::HTTPForwarderOutputPort;

    action def <InitializeAdapter> 'Initialize Adapter' :> CIM::Actions::Initialize {
        in config : CIM::Domain::Configuration;
        in :> self : HL7AdapterService;
        doc /* Bindings and service reference; then start listeners (MLLP, RestApi) per state machine do action; wire component events to service dispatch and current-message state. */
        rep functionBody language "TypeScript"
        /*
  this.operationalStore.initializeFromBinding(config.operationalStore);
  this.restApi.initializeFromBinding(this);
  this.mllpReceiver.startReceiver();
  this.parser.initializeFromBinding();
  this.transformer.initializeFromBinding();
  this.httpForwarder.initializeFromBinding();

  this.mllpReceiver.on('transition', (ev: { signal: string }) => {
    if (ev.signal === 'MLLPFrameReceivedSignal') this.dispatch('MLLPFrameReceivedSignal');
    if (ev.signal === 'ListenerStartSignal') this.dispatch('ListenerStartSignal');
  });
  this.mllpReceiver.on('frameComplete', (arg: { payload: Buffer; respond: (accept: boolean) => void }) => {
    this._currentFrame = arg.payload;
    this._pendingRespond = arg.respond;
    this.dispatch('MLLPFrameCompleteSignal');
  });

  this.parser.on('parseComplete', (data) => {
    if (this._pendingRespond) { this._pendingRespond(true); this._pendingRespond = undefined; }
    this._currentParsed = data;
    this.dispatch('MLLPHandlerCompleteSignal');
  });
  this.parser.on('parseFailed', (err?: { message?: string } | string) => {
    if (this._pendingRespond) { this._pendingRespond(false); this._pendingRespond = undefined; }
    const detail = (err && typeof err === 'object' && err.message) ? err.message : (typeof err === 'string' ? err : 'Parse failed');
    const ts = new Date().toISOString();
    this.operationalStore.recordStoreError(this._currentMessageId, 'ParseError', detail, ts);
    this.operationalStore.updateMessageStatus(this._currentMessageId, 'failed');
    this.dispatch('MLLPHandlerFailedSignal');
  });

  this.transformer.on('transformComplete', (jsonStr: string) => {
    this._currentJson = jsonStr;
    this.dispatch('HL7TransformerCompleteSignal');
  });
  this.transformer.on('transformFailed', (err?: string) => {
    const detail = (err != null && err !== '') ? err : 'Transform failed';
    const ts = new Date().toISOString();
    this.operationalStore.recordStoreError(this._currentMessageId, 'ValidationError', detail, ts);
    this.operationalStore.updateMessageStatus(this._currentMessageId, 'failed');
    this.dispatch('HL7TransformerFailedSignal');
  });

  this.httpForwarder.on('deliverySuccess', () => {
    this.dispatch('HTTP2xxSignal');
  });
  this.httpForwarder.on('deliveryFailed', (err?: { message?: string; status?: number }) => {
    const status = err?.status;
    const code = status != null && status >= 400 && status < 500 ? 'HTTP_CLIENT_ERROR' : status != null && status >= 500 ? 'HTTP_SERVER_ERROR' : 'CONNECTION_ERROR';
    const errorClass = status != null && status >= 400 && status < 500 ? 'HTTPClientError' : status != null && status >= 500 ? 'HTTPServerError' : 'ConnectionError';
    const detail = err?.message ?? 'Delivery failed';
    const ts = new Date().toISOString();
    const integrationError = { code, messageText: detail, isRecoverable: false, occurredAt: ts, statusCode: status, messageId: this._currentMessageId };
    this.operationalStore.recordStoreError(this._currentMessageId, errorClass, detail, ts);
    this.operationalStore.updateMessageStatus(this._currentMessageId, 'failed');
    this.errorHandler.handleIntegrationError(integrationError);
    this.dispatch('HTTP5xxOrNetworkErrorSignal');
  });

  this.dispatch('ServiceStartedSignal');
        */
    }

    action def <RecordMessageReceived> 'Record Message Received' {
        in :> self : HL7AdapterService;
        doc /* Extract message_id from HL7 MSH-10 (Message Control ID) when present; store in OperationalStore, record metrics, pass frame to Parser. */
        rep functionBody language "TypeScript"
        /*
  const raw = this._currentFrame;
  const rawStr = raw ? raw.toString('utf8') : '';
  const controlId = rawStr ? this.parser.getMessageControlId(rawStr) : undefined;
  this._currentMessageId = (controlId && controlId.trim()) ? controlId.trim() : `${Date.now()}-${Math.random().toString(36).slice(2)}`;
  const receivedAt = new Date().toISOString();
  const rawLength = raw?.length ?? 0;
  this.operationalStore.insertMessage(this._currentMessageId, receivedAt, 'received', undefined, undefined, rawLength);
  this.errorHandler.recordMessageReceived();
  if (raw) this.parser.handleIncomingMessage(rawStr);
        */
    }

    action def <RecordMessageParsed> 'Record Message Parsed' {
        in :> self : HL7AdapterService;
        doc /* Update store to parsed, record metrics, store metadata and demographics from parsed MSH/PID, pass parsed data to Transformer. */
        rep functionBody language "TypeScript"
        /*
  const parsed = this._currentParsed as { msh: { sendingApplication?: string; sendingFacility?: string; receivingApplication?: string; receivingFacility?: string; messageType?: string; messageControlId?: string }; pid?: { patientIdList?: string; patientName?: string; dateOfBirth?: string; sex?: string } } | undefined;
  this.operationalStore.updateMessageStatus(this._currentMessageId, 'parsed');
  if (parsed && parsed.msh) {
    const m = parsed.msh;
    const metadata = { sendingApplication: m.sendingApplication ?? '', sendingFacility: m.sendingFacility ?? '', receivingApplication: m.receivingApplication ?? '', receivingFacility: m.receivingFacility ?? '', messageType: m.messageType ?? '', messageControlId: m.messageControlId ?? '' };
    const pid = parsed.pid;
    const demographics = pid ? (() => { const n = (pid.patientName ?? '').split('^'); return { patientId: pid.patientIdList ?? undefined, givenName: n[1] || undefined, familyName: n[0] || undefined, dateOfBirth: pid.dateOfBirth ?? undefined, gender: pid.sex ?? undefined }; })() : undefined;
    this.operationalStore.updateMessageDetail(this._currentMessageId, metadata, demographics);
  }
  this.errorHandler.recordMessageParsed();
  this.parser.dispatch('ResetComponentSignal');
  this.transformer.handleTransformRequest(this._currentParsed as any);
        */
    }

    action def <RecordMessageTransformed> 'Record Message Transformed' {
        in :> self : HL7AdapterService;
        doc /* Update store to transformed, record metrics, send JSON to HTTPForwarder. Uses _currentJson and _currentMessageId. */
        rep functionBody language "TypeScript"
        /*
  this.operationalStore.updateMessageStatus(this._currentMessageId, 'transformed');
  this.errorHandler.recordMessageTransformed();
  this.transformer.dispatch('ResetComponentSignal');
  const json = this._currentJson;
  if (json) this.httpForwarder.sendJSONPayload(json);
        */
    }

    action def <RecordMessageDelivered> 'Record Message Delivered' {
        in :> self : HL7AdapterService;
        doc /* Update store to delivered and record metrics. Called after HTTPForwarder emits success. */
        rep functionBody language "TypeScript"
        /*
  this.operationalStore.updateMessageStatus(this._currentMessageId, 'delivered');
  this.errorHandler.recordMessageDelivered();
  this.httpForwarder.dispatch('ResetComponentSignal');
        */
    }
}
